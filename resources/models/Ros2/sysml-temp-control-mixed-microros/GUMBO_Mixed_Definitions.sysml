package GUMBO_Mixed_Definitions {
  language "GUMBO" /*{
    library
      functions

        def aboveAbsoluteZero(degrees: Base_Types::Float_32): Base_Types::Boolean := 
          degrees > -459.67 [f32];
  }*/
}
